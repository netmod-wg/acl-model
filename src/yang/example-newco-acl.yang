module example-newco-acl {

  yang-version 1.1;

  namespace "http://example.com/ns/example-newco-acl";

  prefix example-newco-acl;

  import ietf-access-control-list {
    prefix "acl";
  }

  organization
    "Newco model group.";

  contact
    "abc@newco.com";
  description
    "This YANG module augments IETF ACL Yang.";

  revision YYYY-MM-DD {
    description
      "Creating NewCo proprietary extensions to ietf-acl model";

    reference
      "RFC XXXX: Network Access Control List (ACL)
       YANG Data  Model";
  }

  augment "/acl:acls/acl:acl/" +
          "acl:aces/acl:ace/" +
          "acl:matches" {
    description "Newco proprietary simple filter matches";
    choice protocol-payload-choice {
      description "Newco proprietary payload match condition";
      list protocol-payload {
        key value-keyword;
        ordered-by user;
        description "Match protocol payload";
        uses match-simple-payload-protocol-value;
      }
    }

    choice metadata {
      description "Newco proprietary interface match condition";
      leaf packet-length {
        type uint16;
        description "Match on packet length";
      }
    }
  }

  augment "/acl:acls/acl:acl/" +
          "acl:aces/acl:ace/" +
          "acl:actions" {
    description "Newco proprietary simple filter actions";
    choice action {
      description "";
      case count {
        description "Count the packet in the named counter";
        leaf count {
          type uint32;
          description "Count";
        }
      }
      case policer {
        description "Name of policer to use to rate-limit traffic";
        leaf policer {
          type string;
          description "Name of the policer";
        }
      }
      case hiearchical-policer {
        leaf hierarchitacl-policer {
          type string;
          description
            "Name of the hierarchical policer.";
        }
        description
          "Name of hierarchical policer to use to
           rate-limit traffic";
      }
    }
  }

  augment "/acl:acls/acl:acl" +
          "/acl:aces/acl:ace/" +
          "acl:actions" {
    leaf default-action {
      type identityref {
        base acl:forwarding-action;
      }
      default acl:drop;
      description
        "Actions that occur if no ace is matched.";
    }
    description
      "Newco proprietary default action";
  }

  grouping match-simple-payload-protocol-value {
    description "Newco proprietary payload";
    leaf value-keyword {
      type enumeration {
        enum icmp {
          description "Internet Control Message Protocol";
        }
        enum icmp6 {
          description 
            "Internet Control Message Protocol 
             Version 6";
        }
        enum range {
          description "Range of values";
        }
      }
      description "(null)";
    }
  }
}
